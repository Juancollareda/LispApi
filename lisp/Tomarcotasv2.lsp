(defun c:ExCotas()
(vl-load-com)
(setq valor (getint "\n cantidad de midas a tomar (se recordar mide alt y altura): "))
(setq Nom (getstring "\n Nombre de figura: "))
(setq test 1)
(setq indice 0)
(setq d '("a" "b" "c" "e" "d" "f" "g" "h"))
(while (<= test valor)
(setq pto1(getpoint "\n dame un punto altura : "))
(setq pto2(getpoint "\n dame otro punto altura2 :"))
(setq distancia (rtos(distance pto1 pto2)))
(setq pto1(getpoint "\n dame un punto largo : "))
(setq pto2(getpoint "\n dame otro punto largo2 :"))
(setq distancia2 (rtos(distance pto1 pto2)))
(setq x (car(entsel "\n elija objeto: ")))
(setq vlaobj (vlax-ename->vla-object x))
(setq num (vlax-get-property vlaobj 'Area))
(setq area (rtos(* 1.0 num ) 2))
(setq archivo (open "C:\\Users\\usuario\\Desktop\\Area6.csv" "a"))
(write-line (strcat "\n" Nom "\n") archivo)
(setq Letra (nth indice d))
(write-line (strcat    "Imagen Del plano" "," "Tramo"  "," "Altura" "," "longitud" "," "Area") archivo)
(write-line (strcat    "," Letra "," distancia ","distancia2 ","    area) archivo)
(close archivo)
(setq test (1+ test))
(setq indice (1+ indice))
)
)
